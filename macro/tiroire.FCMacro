# -*- coding: utf-8 -*-

import FreeCAD,FreeCADGui,Part,os,pathlib
 
# CHANGE THE LINE BELOW
path_to_ui = "tiroire.ui"
 
class DimenssionTiroire:
	def __init__(self, inside_width, outside_width, slide_lenght, height, thickness, bottom_thickness):
		self.width = inside_width - 12
		self.depth = slide_lenght - 10
		self.height = height
		self.thickness = thickness
		self.bottom_thickness = bottom_thickness
		self.bottom = 30
		self.gap = (outside_width-inside_width)/2
   
class DimenssionFace:
	def __init__(self, outside_width, outside_height, depth):
		self.gap = 3		
		self.width = outside_width - 2 * self.gap
		self.height = outside_height - 2 * self.gap
		self.depth = depth

class TiroireTask:
	def __init__(self):
		# this will create a Qt widget from our ui file
		dir = os.path.dirname(os.path.abspath(__file__))
		print(dir + "/" + path_to_ui)
		self.form = FreeCADGui.PySideUic.loadUi(dir + "/" + path_to_ui)
		self.form.setWindowTitle("Tiroire")
 
	def accept(self):
		label = self.form.label_edit.text()
		tiroire = DimenssionTiroire(self.form.inside_width.value(), self.form.outside_width.value(), self.form.slide_lenght.value(), self.form.tiroire_height.value(), self.form.tiroire_thickness.value(), self.form.tiroire_bottom_thickness.value())
		face = DimenssionFace(self.form.outside_width.value(), self.form.outside_height.value(), self.form.tiroire_thickness.value())
		self.blockTiroirePanel(label, tiroire, face)
		FreeCADGui.Control.closeDialog()

	def panel(self, doc, label, dimenssion, position):
		panel = doc.newObject("Part::Box")
		panel.Label = label
		panel.Length = dimenssion[0]
		panel.Width = dimenssion[1]
		panel.Height = dimenssion[2]
		panel.Placement = App.Placement(App.Vector(position[0],position[1],position[2]),App.Rotation(App.Vector(0.0000,0.0000,1.0000),0.0000))
		doc.recompute()

	def blockTiroirePanel(self, label, tiroire, face):
		activeDoc = App.activeDocument();
		obj = activeDoc.addObject('App::Part', label)
		obj.Label = label
		activeDoc.Tip = obj
		self.panel(obj, label  + "_face", (face.width, face.depth, face.height), (face.gap, 0, face.gap))

		self.panel(obj, label  + "_front", (tiroire.width - 2*tiroire.thickness, tiroire.thickness, tiroire.height - tiroire.bottom_thickness), (tiroire.gap + tiroire.thickness, face.depth, tiroire.bottom + tiroire.bottom_thickness + tiroire.gap))
		self.panel(obj, label  + "_back", (tiroire.width - 2*tiroire.thickness, tiroire.thickness, tiroire.height - tiroire.bottom_thickness), (tiroire.gap + tiroire.thickness, face.depth + tiroire.depth - tiroire.thickness, tiroire.bottom + tiroire.bottom_thickness + tiroire.gap))
		self.panel(obj, label  + "_left", (tiroire.thickness, tiroire.depth, tiroire.height+10), (tiroire.gap, face.depth, tiroire.bottom + tiroire.gap-10))
		self.panel(obj, label  + "_right", (tiroire.thickness, tiroire.depth, tiroire.height+10), (tiroire.gap + tiroire.width - tiroire.thickness, face.depth, tiroire.bottom + tiroire.gap-10))
		self.panel(obj, label  + "_bottom", (tiroire.width - 2*tiroire.thickness, tiroire.depth,tiroire.bottom_thickness), (tiroire.gap + tiroire.thickness, face.depth, tiroire.bottom + tiroire.gap))
		activeDoc.recompute()

tiroire = TiroireTask()
#panel.form.show()
FreeCADGui.Control.showDialog(tiroire)
