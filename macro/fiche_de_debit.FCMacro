# -*- coding: utf-8 -*-

import FreeCAD, FreeCADGui, Draft, Spreadsheet,os,pathlib
NUMER_FORMAT = "{:.2f}"

class Line:
	def __init__(self):
		self.qt = 1

class DebitCardGroup:

	indexGroup = 'z'

	def __init__(self, group, lines):
		DebitCardGroup.indexGroup = self.nextIndexGroup()
		self.label = group
		self.lines = []
		self.surfaces = {}
		self.volum = 0
		for line in lines:
			line.index = self.indexGroup+str(len(self.lines) + 1)
			if line.getThickness() in self.surfaces.keys():				
				self.surfaces[line.getThickness()] = self.surfaces[line.getThickness()]+ line.getSurface()
			else:
				self.surfaces[line.thickness.Value] = line.getSurface()
			self.volum = self.volum + line.getVolum()
			self.lines.append(line)
			
	def nextIndexGroup(self):
		return chr((ord(DebitCardGroup.indexGroup.upper())+1 - 65) % 26 + 65)

class DebitCardLine:
	
	def __init__(self, label, partLenght, partWidth, partHeight, material):
		self.index = 1
		self.label = label
		self.qt = 1
		dimension = [partLenght, partWidth, partHeight]
		dimension.sort()
		self.length = dimension[1]
		self.width = dimension[2]
		self.thickness = dimension[0]
		self.material = material

	def getLengthDebit(self):
		return self.length.Value + 5

	def getWidthDebit(self):
		return self.width.Value + 5

	def getThicknessDebit(self):
		return self.thickness.Value + 5

	def getDebit(self):
		return '{:d} - {:.{w}f}x{:.{w}f}x{:.{w}f} {unit}³'.format(self.qt, self.getLengthDebit(), self.getWidthDebit(), self.getThicknessDebit(), w=0, unit = Units.Metre.getUserPreferred()[2])

	def getSurface(self, unit = "m^2"):
		surface = self.length * self.width
		return  surface.getValueAs(unit)

	def getVolum(self, unit = "m^3"):
		volum = self.length * self.width * self.thickness
		return  volum.getValueAs(unit)

	def getLength(self):
		return str(self.length) 

	def getWidth(self):
		return str(self.width)

	def getThickness(self):
		return str(self.thickness)
	
	def __eq__(self, other):
		return self.length == other.length and self.width == other.width and self.thickness == other.thickness and self.material == other.material

		

class DebitCardSpreadsheet:
	def __init__(self, activeDoc):
		self.sheet = activeDoc.addObject('Spreadsheet::Sheet','Fiche de debit')
		self.cl=1
		self.buildTitle('FICHE DE DEBIT -  ' +activeDoc.Label)
		self.buildTableHeader()

	def buildTable(self, groups):
		surfacesTot = {}
		volumTot = 0
		for group in groups:
			self.buildTitle(group.label)
			for line in group.lines:
				self.buildLine(line)
			self.buildFooterCalculateLines(group.surfaces, group.volum)
			for surface in group.surfaces:
				if surface in surfacesTot.keys():				
					surfacesTot[surface] = surfacesTot[surface]+ group.surfaces[surface]
				else:
					surfacesTot[surface] = group.surfaces[surface]
			volumTot = volumTot + group.volum
		self.buildFooter(surfacesTot, volumTot)

	def nextCl(self):
		self.cl = self.cl + 1

	def getCl(self):
		return str(self.cl)

	def buildTitle(self, title):
		self.sheet.mergeCells('A'+self.getCl()+':H'+self.getCl())
		self.sheet.setAlignment('A'+self.getCl()+':H'+self.getCl(), 'center', 'keep')
		self.sheet.setStyle('A'+self.getCl()+':H'+self.getCl(), 'bold', 'add')
		self.sheet.set('A'+self.getCl()+':H'+self.getCl(), title)
		self.nextCl()

	def buildTableHeader(self):
		self.sheet.setStyle('A'+self.getCl()+':H'+self.getCl(), 'bold', 'add')
		self.sheet.setForeground('A'+self.getCl()+':H'+self.getCl(), (1,1,1))
		self.sheet.setBackground('A'+self.getCl()+':H'+self.getCl(), (0,0.45,0))

		self.sheet.set('A'+self.getCl(), 'N°')
		self.sheet.setColumnWidth('A', 40)
		self.sheet.set('B'+self.getCl(), 'Désignation')
		self.sheet.setColumnWidth('B', 150)
		self.sheet.set('C'+self.getCl(), 'Qté')
		self.sheet.setColumnWidth('C', 60)
		self.sheet.set('D'+self.getCl(), 'Long.')
		self.sheet.setColumnWidth('D', 110)
		self.sheet.set('E'+self.getCl(), 'Larg.')
		self.sheet.setColumnWidth('E', 110)
		self.sheet.set('F'+self.getCl(), 'Ep.')
		self.sheet.setColumnWidth('F', 110)
		self.sheet.set('G'+self.getCl(), 'Matière')
		self.sheet.set('H'+self.getCl(), 'Dimension debit')
		self.sheet.setColumnWidth('H', 150)
		self.nextCl()

	def buildLine(self, line):
		self.sheet.setRowHeight(self.getCl(),  line.qt * 22)
		self.sheet.set('A'+self.getCl(), line.index)
		self.sheet.set('B'+self.getCl(), line.label)
		self.sheet.set('C'+self.getCl(), str(line.qt))
		self.sheet.set('D'+self.getCl(), line.getLength())
		self.sheet.set('E'+self.getCl(), line.getWidth())
		self.sheet.set('F'+self.getCl(), line.getThickness())
		self.sheet.set('G'+self.getCl(), line.material)
		self.sheet.set('H'+self.getCl(), line.getDebit())

		self.nextCl()
	
	def buildFooterCalculateLines(self, surfaces, volum):
		self.sheet.set('G'+self.getCl(), "Volume")
		self.sheet.set('H'+self.getCl(), '{:.3f} m³'.format(volum.Value))
		for i in surfaces:
			self.sheet.setStyle('A'+self.getCl()+':H'+self.getCl(), 'bold', 'add')
			self.sheet.mergeCells('C'+self.getCl()+':D'+self.getCl())
			self.sheet.set('C'+self.getCl()+':D'+self.getCl(), 'Surface (ep. {:g})'.format(i))
			self.sheet.set('E'+self.getCl(), '{:.3f} m²'.format(surfaces[i].Value))
			self.nextCl()

	def buildFooter(self, surfaces, volum):
		self.buildTitle("TOTAUX")
		self.buildFooterCalculateLines(surfaces, volum)

class DebitCard:
	
	def __init__(self, activeDoc):
		self.activeDoc = activeDoc
		self.groups = []
		objs = activeDoc.Objects
		for part in objs:
			if part.isDerivedFrom("App::Part"):
				lines = []
				for obj in part.Group:
					if obj.isDerivedFrom("Part::Box"):
						line = DebitCardLine(obj.Label, obj.Length, obj.Width, obj.Height, "/")
						if line in lines:
							lineQtUp = lines[lines.index(line)]
							lineQtUp.qt = lineQtUp.qt + 1
							lineQtUp.label = lineQtUp.label + "\n" + line.label
						else:
							lines.append(line)	
				self.groups.append(DebitCardGroup(obj.Label, lines))

	def build(self):
		FreeCAD.Console.PrintMessage("Ne pas oublier de changer la précision dans les préférences!\n")
		sheet = DebitCardSpreadsheet(activeDoc)
		sheet.buildTable(self.groups)
		activeDoc.recompute()


activeDoc = App.ActiveDocument
debitCard = DebitCard(activeDoc)
debitCard.build()
